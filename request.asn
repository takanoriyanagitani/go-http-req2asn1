HttpRequest DEFINITIONS ::= BEGIN

	HttpMethod ::= ENUMERATED {
		unspecified (0),
		get (1),
		head (2),
		post (3),
		put (4),
		patch (5),
		delete (6),
		connect (7),
		options (8),
		trace (9)
	}

	HeaderItem ::= SEQUENCE {
		key IA5String,
		val UTF8String
	}

	SimpleRequest ::= SEQUENCE {
		--method 	 HttpMethod,
		method 	 INTEGER,
		url    	 UTF8String,
		protocol IA5String,
		contentLength INTEGER,
		host UTF8String,
		remoteAddr IA5String,
		headers SEQUENCE OF HeaderItem
	}

END
